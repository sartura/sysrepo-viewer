module sysrepo-viewer-example {

  yang-version "1.1";

  namespace "http://sysrepo-viewer.com/example";

  prefix "sve";

  container test-container {
    list names {
      key "index";

      leaf index {
        type uint8;
      }

      leaf name {
        type string {
          pattern "[a-z][a-z\\-]+[a-z]" {
            error-message "must be number in words";
          }
        }
      }
    }

    leaf valid {
      type boolean;
      default false;
    }
  }
}
